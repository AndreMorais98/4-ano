EVENTOS-MIB DEFINITIONS ::= BEGIN

IMPORTS
	accountingControlMIB
		FROM ACCOUNTING-CONTROL-MIB
	MODULE-IDENTITY,
	OBJECT-TYPE,
	Counter32
		FROM SNMPv2-SMI
	OBJECT-GROUP
		FROM SNMPv2-CONF;

grEventosMIB MODULE-IDENTITY
	LAST-UPDATED "202102251522Z"	-- Feb 25, 2021, 3:22:00 PM
	ORGANIZATION ""
	CONTACT-INFO
		""
	DESCRIPTION
		""
	REVISION "202102251522Z"	-- Feb 25, 2021, 3:22:00 PM
	DESCRIPTION
		"Initial version."
	-- 1.3.6.1.2.1.60.10
	::= { accountingControlMIB 10 }


-- Conformance
--

grEventosConf OBJECT IDENTIFIER 
	-- 1.3.6.1.2.1.60.10.3
	::= { grEventosMIB 3 }

-- Groups
--

grEventosGroups OBJECT IDENTIFIER 
	-- 1.3.6.1.2.1.60.10.3.1
	::= { grEventosConf 1 }

-- Compliances
--

grEventosCompliances OBJECT IDENTIFIER 
	-- 1.3.6.1.2.1.60.10.3.2
	::= { grEventosConf 2 }

grEventosTable OBJECT-TYPE
	SYNTAX  SEQUENCE OF GrEventosEntry
	MAX-ACCESS not-accessible
	STATUS  current
	DESCRIPTION
		"Tabela de eventos"
	-- 1.3.6.1.2.1.60.10.4
	::= { grEventosMIB 4 }


grEventosEntry OBJECT-TYPE
	SYNTAX  GrEventosEntry
	MAX-ACCESS not-accessible
	STATUS  current
	DESCRIPTION
		"Entrada na tabela com informação do evento"
	INDEX {
		index }
	-- 1.3.6.1.2.1.60.10.4.1
	::= { grEventosTable 1 }


GrEventosEntry ::= SEQUENCE {

	index     Counter32,
	descricao OCTET STRING,
	mensagem  INTEGER }


index OBJECT-TYPE
	SYNTAX  Counter32
	MAX-ACCESS read-only
	STATUS  current
	DESCRIPTION
		"Indice do evento,"
	-- 1.3.6.1.2.1.60.10.4.1.1
	::= { grEventosEntry 1 }


descricao OBJECT-TYPE
	SYNTAX  OCTET STRING
	MAX-ACCESS read-only
	STATUS  current
	DESCRIPTION
		"Descrição do evento"
	-- 1.3.6.1.2.1.60.10.4.1.2
	::= { grEventosEntry 2 }


mensagem OBJECT-TYPE
	SYNTAX  INTEGER
	MAX-ACCESS read-only
	STATUS  current
	DESCRIPTION
		"Mensagem de alerta."
	-- 1.3.6.1.2.1.60.10.4.1.3
	::= { grEventosEntry 3 }


tempoTable OBJECT-TYPE
	SYNTAX  SEQUENCE OF TempoEntry
	MAX-ACCESS not-accessible
	STATUS  current
	DESCRIPTION
		"Tabela com tempo que falta/passou dos eventos."
	-- 1.3.6.1.2.1.60.10.5
	::= { grEventosMIB 5 }


tempoEntry OBJECT-TYPE
	SYNTAX  TempoEntry
	MAX-ACCESS not-accessible
	STATUS  current
	DESCRIPTION
		""
	INDEX {
		index }
	-- 1.3.6.1.2.1.60.10.5.1
	::= { tempoTable 1 }


TempoEntry ::= SEQUENCE {

	anos    INTEGER,
	meses   INTEGER,
	semanas INTEGER,
	dias    INTEGER,
	horas   INTEGER,
	minutos INTEGER }


anos OBJECT-TYPE
	SYNTAX  INTEGER
	MAX-ACCESS read-only
	STATUS  current
	DESCRIPTION
		"Anos"
	-- 1.3.6.1.2.1.60.10.5.1.1
	::= { tempoEntry 1 }


meses OBJECT-TYPE
	SYNTAX  INTEGER
	MAX-ACCESS read-only
	STATUS  current
	DESCRIPTION
		"Meses"
	-- 1.3.6.1.2.1.60.10.5.1.2
	::= { tempoEntry 2 }


semanas OBJECT-TYPE
	SYNTAX  INTEGER
	MAX-ACCESS read-only
	STATUS  current
	DESCRIPTION
		"Semanas"
	-- 1.3.6.1.2.1.60.10.5.1.3
	::= { tempoEntry 3 }


dias OBJECT-TYPE
	SYNTAX  INTEGER
	MAX-ACCESS read-only
	STATUS  current
	DESCRIPTION
		"Dias"
	-- 1.3.6.1.2.1.60.10.5.1.4
	::= { tempoEntry 4 }


horas OBJECT-TYPE
	SYNTAX  INTEGER
	MAX-ACCESS read-only
	STATUS  current
	DESCRIPTION
		"horas"
	-- 1.3.6.1.2.1.60.10.5.1.5
	::= { tempoEntry 5 }


minutos OBJECT-TYPE
	SYNTAX  INTEGER
	MAX-ACCESS read-only
	STATUS  current
	DESCRIPTION
		"Minutos"
	-- 1.3.6.1.2.1.60.10.5.1.6
	::= { tempoEntry 6 }


grEventosBasicGroup OBJECT-GROUP
	OBJECTS {
		index,
		descricao,
		mensagem,
		anos,
		meses,
		semanas,
		dias,
		horas,
		minutos }
	STATUS  current
	DESCRIPTION
		"Basic objects."
	-- 1.3.6.1.2.1.60.10.3.1.1
	::= { grEventosGroups 1 }

END
